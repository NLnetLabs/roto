module rotonda-conf {
  yang-version 1.1;
  namespace "urn:nlnetlabs:rotonda:conf";
  prefix "rotonda";

  import ietf-yang-schema-mount {
    prefix yangmnt;
  }

  typedef "ip-address-origin" {
    type uint32;
  }

  typedef 'ipx-address-origin' {
    type uint8;
  }

  container "rotonda-root" {
    typedef 'ip-address-origin' {
      type uint64;
    }
    leaf rotonda-id {
      type uint8;
      mandatory true;
      config false;
    }
    yangmnt:mount-point "rotonda-root" {
      description
      "    Root \t \n    \"for\" \\logical network element\\" + " and some
       more shit";
    }
  }
}

module rotonda-running-state {
  yang-version 1.1;
  namespace "urn:nlnetlabs:rotonda:state";
  prefix "rotonda-running-state";

  container "rotonda-state-root" {
    leaf rotonda-id {
      type uint8;
      mandatory true;
      config true;
    }
  }
}
