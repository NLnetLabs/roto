module rotonda-conf {
  yang-version 1.1;
  namespace "urn:nlnetlabs:rotonda:conf";
  prefix "rotonda";

  // import ietf-yang-schema-mount {
  //  prefix yangmnt;
  // }

  import ietf-netconf-acm {
    prefix acm;
  }

  import ietf-inet-types {
    prefix inet;
  }

  import ietf-yang-types {
    prefix yang;
  }

  // import ietf-rpki-rtr {
  //   prefix rtr;
  // }

  typedef "xip-address-origin" {
    type inet:ipv4-prefix;
    //type uint32;
  }

  typedef 'ipx-address-origin' {
    type uint8;
  }

  leaf blaffer {
    type yang:date-and-time;
  }

  typedef horror-show {
    type string;
  }

  container "rotonda-root" {
    typedef 'horror-show' {
      type ipx-address-origin;
    }
    leaf rotonda-id {
      type uint8;
      mandatory true;
      config false;
    }
    yangmnt:mount-point "rotonda-root" {
      description
      "    Root \t \n    \"for\" \\logical network element\\" + " and some
       more shit";
    }
  }

  container "rotonda-non-root" {
    typedef horror-show {
      type uint64;
    }
  
    leaf rotor {
      type horror-show;
    }
  }
}

module test {
  namespace "urn:nlnetlabs:rotonda:test";
  prefix test;
}

submodule rotonda-running-state {
  yang-version 1.1;
  // namespace "urn:nlnetlabs:rotonda:state";
  // prefix "rotonda-running-state";
  belongs-to "ietf-bgp";

  container "rotonda-state-root" {
    leaf rotonda-id {
      type uint8;
      mandatory true;
      config true;
    }
  }
}
