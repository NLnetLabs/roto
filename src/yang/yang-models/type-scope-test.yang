module type-scope-test {
  yang-version 1.1;
  namespace "urn:nlnetlabs:rotonda:conf";
  prefix "rotonda";

  //import ietf-yang-types {
  //   prefix yang;
  //}
  

  //import ietf-rpki-rtr {
  //   prefix rtr;
  //}

  import iana-ssh-public-key-algs {
    prefix sshpka;
  }

  typedef horror-show {
     type uint32;
  }

  container "rotonda-root" {
    typedef horror-show1.9 {
      type uint32;
    }

    leaf hs0 {
      type horror-show1.9;
    }
  }

  container "rotonda-non-root" {
    typedef horror-show2 {
      type uint64 {
        range "80..90 | 100..max" {
          description "blaffer";
        }
      }
    }

    typedef horror-show3 {
      type string {
        length "1..12";
      }
    }
      
    //leaf rotor {
    //  type rtr:ipv4-pfx-len;
    //}

    typedef e-num {
      type enumeration {
        enum one {
          description "the first variant";
          value 1;
        }
        enum two {
          description "the second variant";
          value 2;
        }
      }
    }

    typedef e-num-3 {
      type e-num {
        enum three {
          description "the third and final variant";
          value 3;
        }
      }
    }
  }
}
